# BPSM customer requirements

## CR-001
The BPSM shall report master-cylinder pressure with an accuracy of ±2 % over 0–250 bar.
- ASIL: QM

## CR-002
The BPSM shall flag an invalid pressure value within 10 ms of detecting a sensing fault.
- ASIL: D

## CR-003
The invalid-pressure flag shall be transmitted in the CAN status byte.
- ASIL: D
- derives from -> CR-002
